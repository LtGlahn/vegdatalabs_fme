FME workspace FMEWT_genericExample.fmw

Parameters:
- SourceDataset_CSV = $(FME_MF_DIR)attributeNames.csv   # Source Comma Separated Value (CSV) File(s)

Readers:
- CSV_1: CSV from $(SourceDataset_CSV)

Note: Read all 1450 possible attributes
CSV (reader CSV_1)
    attributes: 1. slått utført dato char(1), 100 tonn-vegnett char(1), 2. slått utført dato char(1), Abonnementstype char(1), Adkomst char(1), Adkomst fra til char(1), Adressetype char(1), Akselavstandsregistrering char(1), Akselerasjon char(1), Aksellast, tele char(1), Akselvektregistrering char(1), Aktuell arbeidsoperasjon char(1), Alarm til VTS ved fjerning av brannslokker char(1), Alder char(1), Alternativ uhellskode char(1), Alvorlighetsgrad char(1), Alvorligste skadegrad char(1), Analysedato char(1), Anbefalt klippeutstyr char(1), Andel med data char(1), Anleggsnummer char(1), Anleggsår char(1), Anmeldelsesnummer char(1), Anriking char(1), Ansiktsside char(1), Anslag (mill kr) char(1), Ansvarlig char(1), Ansvarlig - id char(1), Ansvarlig_strukt char(1), Antall char(1),
      Antall alvorlig skadde char(1), Antall alvorlig skadet char(1), Antall ansikt (inkl av) char(1), Antall armaturer i belysningspkt char(1), Antall armer i rundkjøring char(1), Antall bolter/anker char(1), Antall drepte char(1), Antall drepte i ulykken char(1), Antall dører char(1), Antall element char(1), Antall enheter char(1), Antall etasjer over bakkenivå char(1), Antall ferjelemmer char(1), Antall fundament char(1), Antall gangfeltstaver char(1), Antall hjelpesluker char(1), Antall høydeverdier i tverrprofilet char(1), Antall infoplater char(1), Antall inst.plasser trafikkeksponert char(1), Antall kjørefelt char(1), Antall klosett char(1), Antall lamper char(1), Antall leiligheter trafikkeksponert char(1), Antall lettere skadde char(1), Antall lettere skadet char(1), Antall luft forurensningsplaga pers char(1), Antall løsneområder char(1), Antall meget alvorlig skadde char(1), Antall meget alvorlig skadet char(1), Antall oppsettingsutstyr char(1),
      Antall oppstillingsfelt char(1), Antall oppstillingspl. Forflytningshemmede char(1), Antall oppstillingspl. små kjt. char(1), Antall oppstillingspl. store kjt. char(1), Antall oppstillingsplasser vogntog char(1), Antall oppstillingsplasser, lange char(1), Antall parallelle hovedløp char(1), Antall parkeringsplasser små kjt. char(1), Antall parkeringsplasser store kjt. char(1), Antall personer luftplaget i inst char(1), Antall personer pr bolig char(1), Antall personer pr enhet i ulykke char(1), Antall pærer char(1), Antall rader char(1), Antall radiofrekvenser char(1), Antall rom char(1), Antall romlelinjer char(1), Antall rør inn char(1), Antall stengte døgn char(1), Antall støyplagede pers i institusjon char(1), Antall sykler totalt char(1), Antall tininger char(1), Antall ulykker char(1), Antall ulykker med alvorlig skadde char(1), Antall ulykker med drepte char(1), Antall ulykker med lettere skadde char(1), Antall ulykker med meget alvorlig skadde char(1), Antall viketrekanter char(1), Antall vinduer i vegg mot hovedveg char(1), Antall år char(1),
      Antall, støyplagede personer i bolig char(1), Areal char(1), Areal av fylt sperreområde char(1), Areal gjennomsiktig vegg char(1), Areal grunnflate char(1), Areal tilpasset rullestol char(1), Areal tverrsnitt char(1), Areal, belyst char(1), Areal, kjørbart char(1), Areal, kjørbart øvrig char(1), Areal, overkjørbart char(1), Areal, totalt char(1), Areal, totalt øvrig char(1), Arealtype char(1), Arkiveringskode char(1), Arkivnummer char(1), Arkivreferanse1 char(1), Arkivreferanse2 char(1), Arkivreferanse3 char(1), Armering char(1), Arstid char(1), Art char(1), Artliste char(1), Artsnavn char(1), Askeladden_ID char(1), Avdelingsnavn char(1), Avdelingsnummer char(1), Avgift char(1), Avgifts-/restriksjonsinfo char(1), Avgrensa vinterdrift, fra dato char(1),
      Avgrensa vinterdrift, til dato char(1), Avledningsevne char(1), Avlesingsmetode char(1), Avløp char(1), Avløp til char(1), Avskjæringsledd char(1), Avstand char(1), Avstand fra dekkekant char(1), Avstand fra start char(1), Avstand fra veg char(1), Avstand fra vegkant char(1), Avstand høyre sensor til laser char(1), Avstand innbyrdes char(1), Avstand mellom høydeverdier char(1), Avstand mellom tverrprofil char(1), Avstand personaktivitet char(1), Avstand referanselinje, slutt char(1), Avstand referanselinje, start char(1), Avstand senterlinje char(1), Avstand til nødutgang char(1), Avstand vegkant, slutt char(1), Avstand vegkant, start char(1), Avstand, innbyrdes char(1), Avstrøing char(1), Avvisning char(1), Bakgrunn, kort char(1), Bakkeklaring char(1), Bardunert char(1), Bebyggelse char(1), Bebyggelsestype char(1),
      Befaring, beskrivelse char(1), Begrenset offentlighet char(1), Begrunnelse for utfallet char(1), Behandlende politidistrikt char(1), Belastningselement char(1), Belastningsgrad char(1), Belastningstype char(1), Belegning char(1), Belegning, areal char(1), Belegning, overkjørbart areal char(1), Belegning, type char(1), Belysning char(1), Belyst char(1), Beregnet 3-meter rettholtverdi char(1), Beregnet løpende IRI-verdi char(1), Beregnet maks spordybde char(1), Beregnet maksimal vanndybde char(1), Beregnet sporareal char(1), Beregnet sporbredde char(1), Beregnet tverrfall char(1), Beregningsansvarlig char(1), Beregningsdato char(1), Beregningsinfo char(1), Beregningsmetode for spordybde char(1), Beregningsmodell char(1), Beregningsprogram char(1), Beregningsprogram, versjon char(1), Beskrivelse char(1), Beskrivelse av området char(1), Beskrivelse av vegminnet char(1),
      Beskrivelse, beredskap char(1), Beskrivelse, lokalisering char(1), Beskyttelsesutstyr char(1), Besøksadresse char(1), Betongfasthet char(1), Bevegelse char(1), Bevegelsesklasse char(1), Bilder char(1), Bildetype char(1), Billettautomat char(1), Billettkontor char(1), Blokkert gang/sykkelveg char(1), Blokkert veglengde char(1), Bokstavnummer char(1), Bompengeanlegg_Id char(1), Bomstasjon_Id char(1), Bomstasjonstype char(1), Botanisk navn char(1), Branndør char(1), Brannfarlig char(1), Brannsikker char(1), Bratt over fjellskjæring char(1), Bredde char(1), Bredde arm char(1), Bredde asfaltskulder, høyre char(1), Bredde asfaltskulder, venstre char(1), Bredde dekke, total char(1), Bredde enkeltlinje char(1), Bredde fot char(1), Bredde gjennomsnitt char(1),
      Bredde grusskulder, høyre char(1), Bredde grusskulder, venstre char(1), Bredde kjørebane, del1 char(1), Bredde kjørebane, del11 char(1), Bredde kjørebane, del12 char(1), Bredde kjørebane, del13 char(1), Bredde kjørebane, del14 char(1), Bredde kjørebane, del15 char(1), Bredde kjørebane, del16 char(1), Bredde kjørebane, del2 char(1), Bredde kjørebane, del3 char(1), Bredde kjørebane, del4 char(1), Bredde kjørebane, del5 char(1), Bredde kjørebane, del6 char(1), Bredde kjørebane, total char(1), Bredde krone char(1), Bredde rekkverksrom, høyre char(1), Bredde rekkverksrom, venstre char(1), Bredde trafikkdeler midt char(1), Bredde trafikkdeler, asfaltskulder, høyre char(1), Bredde trafikkdeler, asfaltskulder, venstre char(1), Bredde trafikkdeler, grusskulder, høyre char(1), Bredde trafikkdeler, grusskulder, venstre char(1), Bredde, bunn char(1), Bredde, enkeltlinje char(1), Bredde, firkant char(1), Bredde, gj.snitt char(1), Bredde, gjennomsnitt char(1), Bredde, innvendig char(1), Bredde, målt char(1),
      Bredde, slutt char(1), Bredde, start char(1), Bredde, topp char(1), Bredde, ytre char(1), Bredde1, firkantkum char(1), Bredde2, firkantkum char(1), Brkode1 char(1), Brkode2 char(1), Brukategori char(1), Bruker char(1), Bruksklasse char(1), Bruksklasse tele char(1), Bruksklasse vinter char(1), Bruksnummer char(1), Bruksområde char(1), Brunummer char(1), Brutus_Id char(1), Brøyterodenummer char(1), Brøytet areal char(1), Budsjett char(1), Busstrafikk i makstime char(1), Byggemateriale char(1), Byggeår char(1), Byggverkstype char(1), Bæreevne char(1), Bæreevnegruppe, matrial undergr char(1), Bøyle char(1), CO konsentrasjon 5m fra vegkant char(1), CO pers 15 char(1), CO pers 25 char(1),
      CO pers 8 char(1), Coinsp15 char(1), Coinsp25 char(1), Coinsp8 char(1), Cube-tilknytning char(1), DatabaseID char(1), Dataopprinnelse char(1), Dato char(1), Dato ferdig char(1), Dato for gjennomført tiltak char(1), Dato for innmelding char(1), Dato for målt NO2 char(1), Dato for målt pm10 char(1), Dato for målt støy char(1), Dato fra char(1), Dato generert char(1), Dato grunnlag char(1), Dato kalibrert char(1), Dato kontrollert char(1), Dato registrert char(1), Dato statusendring char(1), Dato til char(1), Dato, fra char(1), Dato, til char(1), Default verdier for rush char(1), Definert dato (ååååmmdd) char(1), Dekkeareal char(1), Dekkebredde char(1), Dekkebredde, gj.snitt char(1), Dekkebredde, maks char(1),
      Dekkebredde, min char(1), Dekkebreddefordeling char(1), Dekkekode char(1), Dekkekvalitet char(1), Dekkeleggingsdato char(1), Dekketemperatur char(1), Dekketykkelse char(1), Dekketype char(1), Dekkevariant char(1), Dekktype char(1), Detektornummer char(1), Diameter char(1), Diameter, indre char(1), Diameter, innvendig char(1), Diameter, ytre char(1), Diameter, åpning char(1), Digitalt char(1), Dimensjon vikesymbol char(1), Dimming char(1), Distribusjon char(1), Dokument oppevares char(1), Dokumentasjon brannfarlighet char(1), Drenering char(1), Dreneringsforhold char(1), Drept char(1), Driftsansvarlig char(1), Driftsattår char(1), Driftsklasse char(1), Driftsmerking char(1), Driftsrelaterte forhold char(1),
      Driftsstatus char(1), Drikkevann char(1), Drivstoffyllingsanlegg char(1), Dusj char(1), Dybde char(1), Dybde til overløp char(1), Dybde til utløp char(1), Dybde under vegkant char(1), Dybde, ytre char(1), Dykker char(1), Dyreart char(1), E-post char(1), Effekt char(1), Egen gangbane til ferje char(1), Egennavn char(1), Eier char(1), Eier, navn char(1), Ekstern referanse char(1), Ekstra belysning inngangssone char(1), Ekvivalent innendørs støynivå char(1), Ekvivalent utendørs støynivå char(1), Elementlengde char(1), Endret av char(1), Endret den char(1), Energikilde char(1), Energitilførsel char(1), Enhet char(1), Enhetens funksjon char(1), Enhetsbokstav char(1), Enhetsnummer char(1),
      Enhetstype char(1), EnvTemp char(1), Envegsregulering char(1), Etableringsår char(1), Etablert passasje char(1), Etterslep HB 111 char(1), F1 ÅDT-faktor char(1), F2 Skredfaktor char(1), F3 Omkjøringsfaktor char(1), F4 Stengningsfaktor char(1), F5 Skredfarefaktor char(1), F6 Naboskredfaktor char(1), F60 char(1), FFid char(1), Fabrikant char(1), Fabrikant pumpe char(1), Fabrikant, motor char(1), Fabrikant, vifteblad char(1), Fabrikant, viftehus char(1), Fare for nedfall char(1), Fare for type ulykke, primært char(1), Fare for type ulykke, sekundært char(1), Farebeskrivelse char(1), Farge char(1), Farge_liste char(1), Fargeliste_TV_tekst char(1), Fargelistenr_TV_tall char(1), Farlig gods char(1), Fartsgrense char(1), Fartsmåler, installeringsår char(1),
      Fartsmåler, type char(1), Fasade avstand char(1), Fasade deknings grad char(1), Fast dekke char(1), Fastmontert char(1), Fellesføring med annen etat char(1), Fellesrute char(1), Fellesvegkode char(1), Feltbeskrivelse char(1), Feltkode char(1), Feltoversikt char(1), Felttype char(1), Ferdig dato char(1), Ferdselsformål char(1), Ferje til char(1), Ferjeleie_Id char(1), Festet på char(1), Fibertilsetning char(1), Filnavn char(1), Filnavn, rådatafil char(1), Filtreringskonstant char(1), Finstoffinnhold char(1), Fjernes i vintersesong char(1), Fjernovervåkning char(1), Fjernstyring char(1), Flatenummer char(1), Flomskred, bredde char(1), Flomskred, frekvens char(1), Folieklasse char(1), Fom. ulykkesdato char(1),
      Forbruk char(1), Fordeling i intervaller char(1), Fordeling i verdier char(1), ForholdLange char(1), ForholdÅDT char(1), Forkiling char(1), Formål char(1), Formål/hensikt med vernet char(1), Forsegling char(1), Forsyningspunkt til andre anlegg char(1), Forvaltningsplan godkjent dato RA char(1), Forvaltningsplan godkjent dato SVV char(1), Forvarming char(1), Forventet maksimal timetrafikk char(1), Fra meter char(1), Fra navn char(1), FraMeter char(1), Framføringsveg char(1), Frekvens Ambulanse VHF, RX char(1), Frekvens Ambulanse VHF, TX char(1), Frekvens Brannvesen VHF, RX char(1), Frekvens Brannvesen VHF, TX char(1), Frekvens Innsnakk char(1), Frekvens NRK P1 char(1), Frekvens NRK P2 char(1), Frekvens NRK P3 char(1), Frekvens P4 char(1), Frekvens Politi VHF, RX char(1), Frekvens Politi VHF, TX char(1), Frekvens Statens Vegvesen VHF, RX char(1),
      Frekvens Statens Vegvesen VHF, TX char(1), Frekvens felles VHF-redningskanal, RX char(1), Frekvens felles VHF-redningskanal, TRX char(1), Fresemetode char(1), Fresingsdato char(1), Friction char(1), Frist (ååååmmdd) char(1), Fullført char(1), Fullskalabilde char(1), Fundamentering char(1), Fundamentering/plassering char(1), Fundamentmateriale char(1), Funksjon char(1), Fylke char(1), Fylkesnavn char(1), Fylkesnummer char(1), Fødselsdato char(1), Føreforhold char(1), Førerkort utstedt første gang char(1), Første berøringspunkt char(1), G.nr/b.nr char(1), GAB-nr char(1), GAB-nummer char(1), Gangavstand til servicetilbud char(1), Gate-/vegnavn char(1), Gateadresse char(1), Gateklasse char(1), Gatekode char(1), Gatenavn char(1), Gatenummer char(1),
      Gebyr for strøm   char(1), Generell kommentar char(1), Generelle bestemmelser char(1), Geofon-1, avstand char(1), Geofon-1, nedbøyning char(1), Geofon-2, avstand char(1), Geofon-2, nedbøyning char(1), Geofon-3, avstand char(1), Geofon-3, nedbøyning char(1), Geofon-4, avstand char(1), Geofon-4, nedbøyning char(1), Geofon-5, avstand char(1), Geofon-5, nedbøyning char(1), Geofon-6, avstand char(1), Geofon-6, nedbøyning char(1), Geofon-7, avstand char(1), Geofon-7, nedbøyning char(1), Geofon-8, avstand char(1), Geofon-8, nedbøyning char(1), Geofon-9, avstand char(1), Geofon-9, nedbøyning char(1), Geografisk område char(1), Geografisk oppløsning char(1), Geom, punkt char(1), Geometri, flate char(1), Geometri, linje char(1), Geometri, navn char(1), Geometri, oppdateringsdato char(1), Geometri, punkt char(1), Geometri, punkt 1 char(1),
      Geometri, punkt 2 char(1), Geometri, punkt, bygning char(1), Geometri, verifiseringsdato char(1), Gjelder bane char(1), Gjelder buss char(1), Gjelder drosje char(1), Gjelder rutebåt char(1), Gjennomført tiltak char(1), Gjennomsnittlig avstand fra veg char(1), Gjennomsnittlig avstand til veg char(1), Gjennomsnittlig elementlengde char(1), Gjentakelsesintervall char(1), Glassflater markert char(1), Glassutforming char(1), Godkjent avløp char(1), Graderingstall (Cu) char(1), Gratis gjennomkjøring ved HC-brikke char(1), Grunnforhold char(1), Grunnkretsnavn char(1), Grunnkretsnummer char(1), Grunnlag char(1), Grunnlag for ÅDT char(1), Grøftebredde på skredside char(1), Grøfteklasse char(1), Gummitilsetning char(1), Gyldig fra dato char(1), Gyldighetstidspunkt char(1), Går under char(1), Gårdsnummer char(1), H-min, høyre kant char(1),
      H-min, midt char(1), H-min, venstre kant char(1), HDT char(1), HV, IQR char(1), HV, Median char(1), Har flyteramme char(1), Har innløpsrist char(1), Har parkeringsplass char(1), Hastighet i makstime char(1), Hastighet over døgnet char(1), Hastighetsregistrering char(1), Helning char(1), Helning støtside kjegle char(1), Helning, fjellskjæring char(1), Helning, gjsn char(1), Helning, maks char(1), Helning/Fall char(1), Helningsvarians char(1), Helningsvinkel gjerde char(1), Hendelsesdato char(1), Hendelsestidspunkt char(1), Herkomst, sort char(1), Hevet char(1), Himmelretning char(1), Hinder type char(1), Historisk hp char(1), Historisk kilometerverdi char(1), Historisk vegkategori char(1), Historisk vegnummer char(1), Historisk vegstatus char(1),
      Holdeplassnummer char(1), Horisontalradius, 50 % char(1), Horisontalradius, 90 % char(1), Horisontalradius, midlere char(1), Horisontalradius, minste char(1), Horisontalradius, spormåling char(1), Horisontalradius, største char(1), Horisontalradiusfordeling char(1), Hovedmateriale i vegg mot hovedveg char(1), Hovedparsell char(1), Hovedproblem char(1), Hovedårsak til stengning char(1), Husnummer char(1), Hustype char(1), Hva er ikke tillatt char(1), Hva er tillatt char(1), Hvelvisolasjon char(1), Håndlist char(1), Høyde char(1), Høyde over terreng char(1), Høyde over veg char(1), Høyde over veg, slutt char(1), Høyde over veg, start char(1), Høyde over vegdekke char(1), Høyde over vegkant char(1), Høyde sikringselement char(1), Høyde slutt char(1), Høyde start char(1), Høyde støtside kjegle char(1), Høyde, egen char(1),
      Høyde, firkant char(1), Høyde, gj.snitt char(1), Høyde, gjsn char(1), Høyde, innvendig char(1), Høyde, maks char(1), Høyde, maksimal char(1), Høyde, middel char(1), Høyde, passasje char(1), Høyde, slutt char(1), Høyde, start char(1), Høyde, ytre char(1), Høydeforskjell veg - 1.etg char(1), Høydeforskjell veg/utløsningssted char(1), Høydeposisjon char(1), Høydereferanse char(1), Høydeverdi char(1), Høyfjellsstrekning char(1), I drift char(1), ID eksternt system char(1), IRI-Beregningslengde char(1), IRI-Jevnhetsindeks char(1), IRI-verdi, 50 % char(1), IRI-verdi, 90 % char(1), Id Laser char(1), Id Ultralydbjelke char(1), Id nummer char(1), Id_HP char(1), Id_entry char(1), Igangsettingsdato char(1), Indeks, alle døgn char(1),
      Indeks, helgedøgn char(1), Indeks, yrkesdøgn char(1), Indeksår char(1), Informasjon char(1), Initialer_definert_av char(1), Innfartsparkering char(1), Inngår i drenssystem char(1), Innhold char(1), Innkrevningsretning char(1), Innmelders E-postadresse char(1), Innmelders adresse char(1), Innmelders navn char(1), Innmelders postnr char(1), Innmelders poststed char(1), Innmelders telefonnr char(1), Innmeldertype char(1), Innvendig belysning char(1), Installeringsår char(1), Internt nummer char(1), Intervall char(1), Isnedfall, bredde char(1), Isnedfall, frekvens char(1), Jevnhetsfordeling char(1), Jevnhetsformål char(1), Jevnhetskrav char(1), Jord-/løsmasseskred, bredde char(1), Jord-/løsmasseskred,frekvens char(1), Jordart char(1), Justert_Avvik char(1), Kabler char(1),
      Kabler seksjonert char(1), Kabler sikret v nedgraving char(1), Kafeteria char(1), Kaikantsikring char(1), Kamera, installeringsår char(1), Kamera, type char(1), Kameraovervåkning char(1), Kampanjetype char(1), Kanalisering primærveg char(1), Kanalisering sekundærveger char(1), Kantslått, anbefalt intervall char(1), Kapasitet char(1), Kategori char(1), Kilde char(1), Kilde egenskapstypeID char(1), Kilde for ulykken char(1), Kilde vegobjekttypeID char(1), Kiosk char(1), Kjegleform char(1), Kjennemerke char(1), Kjønn char(1), Kjønn i ulykke char(1), Kjørbar char(1), Kjørebanebredde char(1), Kjørebanebredde, maks char(1), Kjørebanebredde, min char(1), Kjørebanebreddefordeling char(1), Kjørefelt char(1), Kjørefeltbredde char(1), Kjørehastighet v måling char(1),
      Kjøreretning char(1), Kjøretøylengderegistrering char(1), Kjøretøytype char(1), Kjøretøytype, dimensjonerende char(1), Kjøring til eiendommene tillatt char(1), Klappskilt char(1), Klasse char(1), Klassifikasjon av vegstøv belastning char(1), Klassifisering char(1), Klima char(1), Klokkeslett char(1), Klokkeslett start måling char(1), Klokkeslett, fra char(1), Klokkeslett, til char(1), Klotoideparameter char(1), Kollektivtilbud til sentrum char(1), Kolonne antall char(1), Kolonne antall timer char(1), Kolonne fart char(1), Kommentar dekk char(1), Kommune char(1), Kommune 1 char(1), Kommune 2 char(1), Kommunenavn char(1), Kommunenr char(1), Kommunenummer char(1), Kommunesenter char(1), Kommunikasjon char(1), Konfidensnivå, 50 % char(1), Konfidensnivå, 90 % char(1),
      KonfliktID char(1), Konfliktnivå, endelig char(1), Konfliktnivå, etter tiltak char(1), Konfliktnivå, teoretisk char(1), Konfliktnivå, usikkerhet char(1), Konsentrasjon av CO char(1), Konsentrasjon av NO2 char(1), Konsentrasjon av pm10 char(1), Kontaktinfo char(1), Kontollretning char(1), Kontrollert av char(1), Kontrollretning char(1), Koordinatsystem char(1), Koplingsår char(1), Korreksjon innendørsstøy char(1), Korreksjon utendørsstøy char(1), Korrosjonsbeskyttelse char(1), Kortnavn char(1), Kostnad char(1), Kostnad (kkr) char(1), Kostnadsnivå år char(1), Kraft char(1), Krav til antall ulykker char(1), Kronediameter char(1), Krysningstype char(1), Kryssnummer char(1), Kryssveg char(1), Kumform char(1), Kundenummer char(1), Kurveradius char(1),
      Kurvgenversjon char(1), Kvalitet char(1), Kvalitet grunnlag char(1), Kvalitet, ekstra oppmerking, venstre char(1), Kvalitet, geometri char(1), Kvalitet, oppmerking, høyre char(1), Kvalitet, oppmerking, venstre char(1), L5AF Utendørs støynivå char(1), LED, CLO - constant light output (test) char(1), LED, Effekt armatur, totalt (test) char(1), LED, Utskiftbare lys-moduler (test) char(1), LED, antall per armatur (test) char(1), LED, dimming (test) char(1), LED, driftsstrøm, udimmet (test) char(1), LED, effekt per stk (test) char(1), LED, fabrikant (test) char(1), LED, fabrikat driver (test) char(1), LED, fargegjengivelsesindeks (test) char(1), LED, fargetemperatur (test) char(1), LED, optikk (test) char(1), Lagnavn, eksisterende veg char(1), Lagnavn, forsterkning char(1), Lagtykkelse char(1), Lagtype char(1), Lampeinnstilling char(1), Lampetype char(1), Landskapsansvarlig char(1), Landskapstema char(1), Landskapsverdi char(1), Langsgående deling char(1),
      Lden utendørs støynivå char(1), Le/tak char(1), Ledetekst char(1), LedetekstID char(1), Ledig plass char(1), Leggedato char(1), Leggeår char(1), Lengde char(1), Lengde arm char(1), Lengde bunn kjegle char(1), Lengde farled char(1), Lengde gjenlegging char(1), Lengde med full bredde char(1), Lengde omslutningslinje char(1), Lengde primærveg char(1), Lengde sekundærveg char(1), Lengde ulykkespunkt char(1), Lengde ulykkesstrekning char(1), Lengde, kart char(1), Lengde, skiltet char(1), Lengde, ytre char(1), Lengdeklasse char(1), Lengste spenn char(1), Lenkenr char(1), Lensmannsdistriktsnavn char(1), Lensmannsdistriktsnummer char(1), Leverandør char(1), Leverandør pumpe char(1), Leverandør, motor char(1), Leverandør, vifteblad char(1),
      Leverandør, viftehus char(1), Linjemønster char(1), Link char(1), Link til infosider char(1), Link turistveg char(1), Listetype char(1), Lnatt utendørs støynivå char(1), Lnummer char(1), Location char(1), Lokal styring char(1), Lokalisert ved char(1), Lokalitet char(1), Lokalt display, betjeningspanel char(1), Lokalt navn char(1), Lokk/rist, skade char(1), Lokk/rist, type char(1), Lovgrunnlag char(1), Lovlig adkomst char(1), Lufttemperatur char(1), Luktstoffer char(1), Luminans char(1), Luminanskrav char(1), Lydabsorberende char(1), Lydtett char(1), Lysforhold char(1), Lyshoder char(1), Lysregulert char(1), Løpemeter skravur char(1), Løpenummer char(1), Løsneområde char(1),
      Løvfellende/Vintergrønne char(1), MC-skinne char(1), MPD 50 % char(1), MPD, 90 % char(1), MPD, Middelverdi char(1), MPD, Standardavvik char(1), MPD-fordeling char(1), MW Count char(1), MW Pulses/m char(1), MW Speed char(1), Magasinvolum char(1), Maks aksellast, skiltet char(1), Maks kjøretøylengde, skiltet char(1), Maks totalvekt kjøretøy, skiltet char(1), Maks totalvekt modulvogntog char(1), Maks totalvekt tømmertransport char(1), Maks totalvekt vogntog, skiltet char(1), Maks vogntoglengde char(1), Maks vogntoglengde modulvogntog char(1), Maks vogntoglengde tømmertransport char(1), Maks vogntoglengde, skiltet char(1), Maks. lengde for strekninger char(1), Maksimumsdato, grunnlag char(1), Maksverdi char(1), Manuell (ikke-automatisk) styring char(1), Markering av striper char(1), Markeringsskilt påmontert char(1), Marktype char(1), Masseforbruk char(1), Massetype char(1),
      Mastenummer char(1), Matepunktnummer char(1), Materialbetegnelse, overbygning char(1), Materiale char(1), Materiale skjerm char(1), Materiale søyler char(1), Materiale/belegning char(1), Materialtype char(1), Materialtype reparasjon char(1), Materialtype støtside char(1), Materialtype, speil char(1), Med-retning (fra) char(1), Medium char(1), Meldingsdato char(1), Membran char(1), Mengde char(1), Merke slutt char(1), Merke start char(1), Merknad char(1), Merknad restriksjonsklasse char(1), Merknad syklende char(1), Mfaktor char(1), Middelverdi char(1), Midlere IRI-verdi char(1), Midlere MPD-verdi char(1), Midlere Profil Dybde char(1), Midlere andel lange char(1), Midlere dekkebredde char(1), Midlere kjørebanebredde char(1), Midlere vegbredde char(1),
      Midlere ÅDT char(1), Midtdeler char(1), Mikrobilde char(1), Miljø char(1), Minimumsdato, grunnlag char(1), Minimumsverdi char(1), Minste IRI-verdi char(1), Minste MPD-verdi char(1), Minste andel lange char(1), Minste ÅDT char(1), Minstebredde char(1), Mobilkran-vegnett char(1), Mobiltelefon GSM, Netcom char(1), Mobiltelefon GSM, Telenor mobil char(1), Modifisert bindemiddel char(1), Mot-retning (fra) char(1), Motorveg char(1), Motorvegtype char(1), My_min char(1), Målebil char(1), Målebredde char(1), Måledatafilnavn char(1), Måledato char(1), Måleformål char(1), Målemetode char(1), Målemetode grunnlag char(1), Målemetode, bredde char(1), MålepunktID char(1), Målernummer char(1), Målestasjonsnummer char(1),
      Måletidspunkt char(1), Målt % char(1), Målt utvendig NO2-timemiddel char(1), Målt utvendig pm10 char(1), Målt utvendig støy char(1), Møtefri veg char(1), NB merknad char(1), NB områdebeskrivelse char(1), NO2 konsentrasjon 5m fra vegkant char(1), NO2 personer 100 char(1), NO2 personer 200 char(1), NO2 personer 300 char(1), NO2 personer 350 char(1), NO2-kons. 8-ggr-pr-år char(1), NO2in300 char(1), NO2instpr150 8 char(1), NO2pr150 8 char(1), NO2pr400 char(1), NO2pros 8 char(1), NVP nummer char(1), Naboskred char(1), Nattestengt, fra dato char(1), Nattestengt, til dato char(1), NaturbaseID char(1), Naturtype char(1), Navn char(1), Navn 2 char(1), Navn bompengeanlegg char(1), Navn bomstasjon char(1), Navn på kunstner char(1),
      Navn på strekning char(1), Navn vedlikeholdsansvarlig char(1), Navn, detaljert char(1), Navn, overordnet char(1), Navnetype char(1), Nedbøyning, 20cm-avstand char(1), Nedbøyning, senter plate char(1), Nedfresing char(1), Nedre etasjenummer char(1), Nedre høyde char(1), Nedsenket kantstein char(1), Netteier char(1), NextService char(1), Nivå char(1), Nivåforskjell char(1), No2in100 char(1), No2in200 char(1), No2in350 char(1), No2in400 char(1), Normal stilling char(1), Norsk navn char(1), Nr char(1), Nummer char(1), Nummer-indikator char(1), Nærmeste objekt til fjellskjæring char(1), Nødvendig forsterkning char(1), Objektnavn char(1), Objekttyper char(1), Observert nedfall char(1), Offentlig tilgjengelig char(1),
      OilTemp char(1), Ok SSB char(1), Omkjøring char(1), Områdestyring char(1), Områdetype char(1), Operator char(1), Operatør char(1), Oppbevaringsbokser char(1), Oppdatert fra char(1), Oppdragsgiver char(1), Oppgitt antall skadde char(1), Oppgravingsdato char(1), Oppholdsrom char(1), Oppmålt distanse char(1), Opprettet dato char(1), Opprinnelse char(1), Oppsettingsdato char(1), Oppsettingsutstyr char(1), Oppsettingsår char(1), Oppslammingstid char(1), Oppstart handlingsprogram char(1), Optisk ledning char(1), Overfartstid char(1), Overflatebehandling char(1), Overvåking fra VTS char(1), Overvåkning fra betjeningssentral char(1), Overvåkningslinjer, antall char(1), Overvåkningspersonell char(1), Overvåkningstype char(1), P Reg const: char(1),
      Pall char(1), Panel char(1), Pappelger char(1), Passasjer nummer char(1), Passering v ferist char(1), Periode char(1), Permanent char(1), Personer svært plaget av lokal luft char(1), Personer svært plaget av støy char(1), Persons plassering i kjøretøy char(1), Planer char(1), Plannivå char(1), Planteliv char(1), Planteomgivelser char(1), Plantetidspunkt char(1), Plasser reservert handikappede char(1), Plassering char(1), Plassering fresespor char(1), Plassering i teknisk rom char(1), Plassering på bru char(1), Plasseringskode char(1), Platediameter, fallodd char(1), Plexiglass utenpå infoplater char(1), Pm10 konsentrasjon 5m fra vegkant char(1), Pm10-kons. 25-ggr-pr-år char(1), Pm10-kons. 7-ggr-pr-år char(1), Pm10i150 char(1), Pm10i200 char(1), Pm10i300 char(1), Pm10i350 char(1),
      Pm10i70 char(1), Pm10instpr50 25 char(1), Pm10instpr50 7 char(1), Pm10p150 char(1), Pm10p200 char(1), Pm10p300 char(1), Pm10p350 char(1), Pm10p70 char(1), Pm10pr50 25 char(1), Pm10pr50 7 char(1), Pm10pros 25 char(1), Pm10pros 7 char(1), Politidistriktsnavn char(1), Politidistriktsnummer char(1), Polypropylen char(1), Pos1Endret char(1), Pos2Endret char(1), Posisjon char(1), Postadresse char(1), Postnavn char(1), Postnummer char(1), Prefabrikkert char(1), Pressure char(1), Primæraktivitet char(1), Primærbidrag char(1), Prioriteringskategori char(1), Prioriteringstall char(1), Prioritet char(1), Prisnivå char(1), Privat avtale char(1),
      Problembeskrivelse char(1), Problemverdi char(1), Produksjonsår char(1), Produktnavn char(1), Produktnavn motor char(1), Produktnavn pumpe char(1), Produktnummer vifteblad char(1), Produktnummer, motor char(1), Produktnummer, viftehus char(1), Produsent char(1), Produsent/Type char(1), Produsentnavn char(1), Profil HB072 char(1), Profilering char(1), Program 20m-strekning char(1), Program 20m-strekning, versjon char(1), Prosesshistorie char(1), Prøvenummer char(1), Publisertdato char(1), PunktTilknytning char(1), Punkthinder char(1), Punktnavn char(1), Påkjørsler char(1), Påvirkning, beskrivelse char(1), Påvirkning, endelig char(1), Påvirkning, teoretisk char(1), Påvirkning, totalbeskrivelse char(1), Påvirkning, type char(1), Påvirkning, usikkerhet char(1), Påvirkning, vekt char(1),
      R char(1), RAL-kode char(1), Radius char(1), Rapport, ekstra_1 char(1), Rapport, ekstra_2 char(1), Rapport, ekstra_3 char(1), Rapportmalfil char(1), Rapporttype char(1), Referanse andre konflikter char(1), Referanse for char(1), Referansegeometri char(1), Referansenummer char(1), Refleks char(1), Refleksleverandør char(1), RegAvvik char(1), Region char(1), Regionsnavn char(1), Regionsnummer char(1), Registrering status char(1), Registreringsansvarlig char(1), Registreringsdata, referanser char(1), Registreringsdato char(1), Registreringsdato for fagdata char(1), Registreringsland char(1), Registreringsnivå char(1), Registreringsprogram char(1), Registreringsprogram, versjon char(1), Registrert av char(1), Regulering for enhet i vegkryss char(1), Rehabilitering char(1),
      Rekkefølge char(1), Rekkverksbredde char(1), Rekkverkstype char(1), Reklameavtale char(1), Reparert dato char(1), Reserveringssystem  char(1), Resipienttilstand char(1), Resipienttype char(1), Restriksjon grøft/kantrensk char(1), Restriksjonsklasse char(1), Retning char(1), Retningsendring char(1), Retrorefleksjon, målt, bunn char(1), Retrorefleksjon, målt, kant char(1), Risikotype char(1), Risikovurdering char(1), Rosita_id char(1), Rundkjøring, indre diameter char(1), Rundkjøring, ytre diameter char(1), Rushtid ettermiddag, fra char(1), Rushtid ettermiddag, til char(1), Rushtid morgen, fra char(1), Rushtid morgen, til char(1), Rushtidsavgift char(1), Rushtidstakst liten bil char(1), Rushtidstakst stor bil char(1), Rusmiddel char(1), Ruteopplysning char(1), Rutetidsinformasjon char(1), Ryddeintervall char(1),
      Rømningsveg char(1), SCI char(1), SDT char(1), SOSI-filnavn char(1), SOSI-versjon char(1), SPI char(1), SVEISnummer char(1), SW Versjon char(1), Saksbehandler char(1), Saksbehandlingsdato char(1), Saksnummer char(1), Samkjørt char(1), Sektype2 char(1), Sentralt grafisk system char(1), Serienummer char(1), Service-/nødtelefoner til VTS char(1), Sideposisjon char(1), Sideveg char(1), Signatur char(1), Sikkerhetsklasse char(1), Sikkerhetskrav char(1), Sikra areal char(1), Sikt char(1), Siktklasse char(1), Sist kontollmålt char(1), Sist kontrollmålt av char(1), Sist oppdatert fra NorTraf char(1), Sist oppdatert i NorTraf char(1), Siste tiltak char(1), Sittemulighet char(1),
      Skade på bru char(1), Skade på drenering char(1), Skade på kjøretøy char(1), Skade på person char(1), Skade på rekkverk char(1), Skade på vegdekke/vegkropp char(1), Skadeforløp char(1), Skadegrad char(1), Skadegrad fra SSB char(1), Skadegradstetthet, forventet char(1), Skadegradstetthet, normalt char(1), Skadegradstetthet, registrert char(1), Skaderisiko char(1), Skadetype char(1), Skiftet dato char(1), Skifting av budskap char(1), Skilta høyde char(1), Skiltet char(1), Skiltet atkomst char(1), Skiltform char(1), Skiltnummer char(1), Skiltnummer HB-050 char(1), Skiltutforming char(1), Skiltutforming, xml char(1), Skinneutrustning char(1), Skjema 2 SSB char(1), Skjermanlegg, enhetsnummer char(1), Skjermingsgrad char(1), Skjermtetthet char(1), Skjøtemetode char(1),
      Skjøtselsstandard char(1), Skred dato char(1), Skred klokkeslett char(1), Skredtype char(1), Skydekke char(1), Slip% char(1), Snødybde char(1), Snøskred, bredde char(1), Snøskred, frekvens char(1), Sone char(1), Sone 1 sprekkarealandel char(1), Sone 1 sprekkeandel char(1), Sone 2 sprekkarealandel char(1), Sone 2 sprekkeandel char(1), Sone 3 sprekkarealandel char(1), Sone 3 sprekkeandel char(1), Sone 4 sprekkarealandel char(1), Sone 4 sprekkeandel char(1), Sone 5 sprekkarealandel char(1), Sone 5 sprekkeandel char(1), Sone benyttet i luftstøy beregninger char(1), Sonepåslag char(1), Sp char(1), Spenning char(1), Spesial steinmateriale char(1), Spesialasfalt char(1), Spesialformål char(1), Spesiell plassering char(1), Spesiell utbredelsessituasjon char(1), Spesielle problem char(1),
      Spesielt parkeringsformål char(1), Spor char(1), Spor, bjelke char(1), Spor, laser char(1), Sporareal char(1), Sporbredde char(1), Spordybde char(1), Spordybde, 50 % char(1), Spordybde, 90 % char(1), Spordybde, midlere char(1), Spordybde, minste char(1), Spordybde, største char(1), Spordybdefordeling char(1), Sprøytebetong, har lettilslag char(1), Sprøytebetong, har mikrofiber char(1), Sprøytebetong, tykkelse char(1), Stammediameter char(1), Stammehøyde, krav char(1), Standard ÅDT char(1), Standard, NO2 char(1), Standard, PM10 char(1), Standard, faktisk bæreevne char(1), Standard, fri høyde char(1), Standard, gående/syklende char(1), Standard, horisontalkurvatur char(1), Standard, høyfjell char(1), Standard, problemsoner char(1), Standard, rasfare char(1), Standard, samlet, beregnet char(1), Standard, samlet, korrigert char(1),
      Standard, sikkerhetsutstyr, tunnel char(1), Standard, skadegradstetthet char(1), Standard, stamveg gjennom tettbebyggelse char(1), Standard, stigning char(1), Standard, støy, totalt char(1), Standard, vegbredde char(1), Standardklasse char(1), Stasjonering char(1), Status char(1), Status tiltak char(1), Statusvurdering char(1), Statusår char(1), Sted char(1), Sted/Adresse char(1), Stedegen vegetasjon char(1), Stedfestingens nøyaktighet char(1), Stedlig beredskap char(1), Stedsangivelse char(1), Stedsangivelse, fra-til char(1), Stedsbeskrivelse char(1), Stedsforhold char(1), Stedsnavn char(1), Stedsnavnsregister, id char(1), Steinsprang/fjellskred, bredde char(1), Steinsprang/fjellskred, frekvens char(1), Steinstørrelse char(1), Stekningsbeskrivelse, mobilkran-vegnett char(1), Stengning char(1), Stengningdøgn, skredfare char(1), Stengningsfrekvens, skred char(1),
      Stengt fra dato char(1), Stengt fra klokkeslett char(1), Stengt med bommer char(1), Stengt retning char(1), Stengt til dato char(1), Stengt til klokkeslett char(1), Stige char(1), Stigning char(1), Stigning, slutt char(1), Stigning, start char(1), Stillbilder char(1), Stolpeavstand char(1), Stolpefundamentering char(1), Strandmiljø inntakt char(1), StrekningTilknytning char(1), Strekningsbeskrivelse char(1), Strekningsbeskrivelse, modulvogntog char(1), Strekningsbeskrivelse, spesialtransport char(1), Strekningsbeskrivelse, tømmertransport char(1), Strømtilførsel, kategori char(1), Strømtilførsel, type kabel char(1), Strømuttak char(1), Strørodenummer char(1), Styring fra VTS char(1), Styring fra VTS/E-Verk char(1), Styring fra betjeningssentral char(1), Styrke char(1), Styrkeklasse char(1), Størrelse char(1), Største IRI-verdi char(1),
      Største MPD-verdi char(1), Største andel lange char(1), Største ÅDT char(1), Støy bolig inne fra og med 42 dBA char(1), Støy inst inne fra og med 42 dBA char(1), Støy, bolig, inne, 30-35 dBA char(1), Støy, bolig, inne, 35-40 dBA char(1), Støy, bolig, inne, 40-42 dBA char(1), Støy, bolig, ute, 55-60 dBA char(1), Støy, bolig, ute, 60-65 dBA char(1), Støy, bolig, ute, 65-70 dBA char(1), Støy, bolig, ute, fra og med 70 dBA char(1), Støy, inst, inne, 30-35 dBA char(1), Støy, inst, inne, 40-42 dBA char(1), Støy, inst, inne, fra, 35-40 dBA char(1), Støy, inst, ute, 50-55 dBA char(1), Støy, inst, ute, 55-60 dBA char(1), Støy, inst, ute, 60-65 dBA char(1), Støy, inst, ute, 65-70 dBA char(1), Støy, inst, ute, fra og med 70 dBA char(1), Sum lengde alle løp char(1), Sum lengde ramper char(1), Summert kjørefeltlengde char(1), SurfTemp char(1), Svakhet char(1), SvingTilknytning char(1), Sykkelforbud char(1), Sykkelstativ char(1), System som melder tilgjengelig kapasitet char(1), Særskilt brannobjekt fra tidspunkt char(1),
      Sørpeskred, bredde char(1), Sørpeskred, frekvens char(1), Søyleavstand char(1), TW Pulses/m char(1), TW Speed char(1), Tak char(1), Takoverbygg char(1), Takst liten bil char(1), Takst stor bil char(1), Taktype char(1), Tekst char(1), Tekst på plate char(1), Tekst, type char(1), Tekst-/Symbolhøyde char(1), Telefaksnummer char(1), Telefonnr innsnakk char(1), Telefonnummer char(1), Telefonnummer 1 char(1), Telefonnummer 2 char(1), Telegruppe char(1), Tellepunkt, primært char(1), Tellepunkt, sekundært char(1), Tellepunktnummer char(1), Temakode char(1), Temperatur char(1), Temperatur på veg char(1), Tenningssystem char(1), Tennpunktnummer char(1), Terminal / logistikkområde char(1), Terskelverdi char(1),
      Test_TSF char(1), Test_Tilstandsindeks char(1), Test_bilde char(1), Test_bildeserie char(1), Test_binær char(1), Test_dato char(1), Test_dato_liste char(1), Test_lyd char(1), Test_struct_liste_mbilde char(1), Test_tekstblob char(1), Test_video char(1), Tetthet char(1), Tetthetsklasse char(1), Tidsoppløsning char(1), Tidsperiode char(1), Tidsstyrt char(1), Til navn char(1), TilMeter char(1), Til_Meter char(1), Tildekning, fradato char(1), Tildekning, tildato char(1), Tilgang til strøm char(1), Tilknyttet lukka dren char(1), Tilkomst char(1), Tilleggsinformasjon char(1), Tilleggsutstyr char(1), Tilrettelegging handikappede char(1), Tilskudd char(1), Tilstand char(1), Tiltak char(1),
      Tiltak anbefalt char(1), Tiltak når char(1), Tiltak, kommentar char(1), Tiltak, totalbeskrivelse char(1), Tiltaktype char(1), Timesregel char(1), Timestamp char(1), Tittel char(1), Toalett  char(1), Tom. ulykkesdato char(1), Tosidig plate med ulike motiv char(1), Total effekt char(1), Total mastelengde char(1), Total sprekkarealandel char(1), Total sprekkeandel char(1), TotalDist char(1), Totalt antall char(1), Trafikantgruppe char(1), Trafikkarbeidstall char(1), Trafikkmengderegistrering char(1), Trafikkreguleringer char(1), Trafikkretning char(1), Trafikkretning, geografisk char(1), Trafikkretning, nett char(1), Trafikkstyrt char(1), Trafikkøy char(1), Transaksjonstabell char(1), Transportmiddel char(1), Treslag, botanisk navn char(1), Treslag, norsk navn char(1),
      Trinnfri adkomst char(1), Truetkategori char(1), Trådløst internett char(1), Tungtrafikkandel i maks timen char(1), Tunnelklasse, prosjektert char(1), Tunnelnummer char(1), Tunnelprofil char(1), Tverrfall, 50 % char(1), Tverrfall, 90 % char(1), Tverrfall, midlere char(1), Tverrfall, minste char(1), Tverrfall, spormåling char(1), Tverrfall, største char(1), Tverrfallsfordeling char(1), Tverrsnittform char(1), Tverrsnittsform char(1), Tykkelse char(1), Tykkelse overfylling char(1), Tykkelse reparasjon char(1), Tykkelse sprøytbetong char(1), Tykkelse, gjennomsnitt char(1), Type char(1), Type CPU-kort char(1), Type HB 232 char(1), Type I/O char(1), Type bussholdeplass char(1), Type fundament char(1), Type gjennomsiktig vegg char(1), Type hinder char(1), Type innløp char(1),
      Type kommunikasjon char(1), Type kontrollmåling char(1), Type måling char(1), Type naturfare char(1), Type prosjekt char(1), Type skjerm char(1), Type skred char(1), Type sprøytbetong char(1), Type stolpe char(1), Type strategi char(1), Type trafikkontroll char(1), Type tunnelløp char(1), Type tverrsnitt char(1), Type utløp char(1), Type vegkryssing char(1), Type åpning/lukking char(1), Type/form char(1), Type/kategori char(1), Typebetegnelse char(1), Tømmebehov char(1), UN Loccode char(1), URL char(1), Uhell kategori char(1), Uhellskode char(1), Ukedag char(1), Ulykke registrert av char(1), Ulykkesdato char(1), Ulykkesfrekvens char(1), Ulykkestidspunkt char(1), Underlag char(1),
      Undernummer char(1), Undersjøisk char(1), Universell utforming char(1), Universelt utformet char(1), Usikkerhet HDT char(1), Usikkerhet SDT char(1), Usikkerhet YDT char(1), Usikkerhet kostnad char(1), Usikkerhet ÅDT char(1), Utbedret år char(1), Utblokking char(1), Utbredelse char(1), Utbøyningsklasse char(1), Utfall av saksbehandlingen char(1), Utforming char(1), Utforming topp char(1), Utførende char(1), Utført dato char(1), Utgår char(1), Utgår, vedlikeholdsansvarlig char(1), Utgår_ fangvolum, ras char(1), Utgår_Antall enkeltelement char(1), Utgår_Areal char(1), Utgår_Areal gjennomsiktlig vegg char(1), Utgår_Bakskinne char(1), Utgår_Belysning char(1), Utgår_Bredde char(1), Utgår_Bredde arm char(1), Utgår_Byggemåte char(1), Utgår_Detaljutforming, vegg char(1),
      Utgår_Dimensjon char(1), Utgår_Fabrikant char(1), Utgår_Farge char(1), Utgår_Festet på char(1), Utgår_Fri bredde char(1), Utgår_Fundamentering char(1), Utgår_Geometri, linje char(1), Utgår_Geometri, punkt char(1), Utgår_Høyde char(1), Utgår_Installeringsår char(1), Utgår_Kontrolldato char(1), Utgår_Lagnummer char(1), Utgår_Lengde char(1), Utgår_Lengde arm char(1), Utgår_Lengde, element char(1), Utgår_Lengde, full bredde char(1), Utgår_Leverandør char(1), Utgår_Lokal styring char(1), Utgår_Lydreflekterende char(1), Utgår_Lydtett char(1), Utgår_Materiale char(1), Utgår_Materialtype char(1), Utgår_Mengde regn char(1), Utgår_Mengde snø char(1), Utgår_Mengde våt snø/sludd char(1), Utgår_Nedbør siste 3 døgn char(1), Utgår_Nummer char(1), Utgår_Nødlys char(1), Utgår_Nødtelefon til Vegvesenet char(1), Utgår_Nødtelefon til andre char(1),
      Utgår_Overflatebehandling char(1), Utgår_Parkering for char(1), Utgår_Plassering char(1), Utgår_Plasseringskode char(1), Utgår_Produktnavn char(1), Utgår_Radius, slutt char(1), Utgår_Snuplass for brøytebil char(1), Utgår_Spenning char(1), Utgår_Spenning_(feil_enhet) char(1), Utgår_Stengt fra dato char(1), Utgår_Stengt fra klokkeslett char(1), Utgår_Stolpeavstand char(1), Utgår_Stolpeprofil char(1), Utgår_Styring char(1), Utgår_Temperatur v værstasjon char(1), Utgår_Tykkelse char(1), Utgår_Type char(1), Utgår_Type fundament char(1), Utgår_Type gjennomsiktig vegg char(1), Utgår_Type skinne char(1), Utgår_Utblokkingstype char(1), Utgår_Utforming char(1), Utgår_Utforming topp char(1), Utgår_Vedlikeholdsansvarlig char(1), Utgår_Vindretning ved værstasjon char(1), Utgår_Vindstyrke v værstasjon char(1), Utgår_vedlikeholdsansvarlig char(1), Utgår_Åpent fra dato char(1), Utgår_Åpent fra klokkeslett char(1), Utleggerarmens lengde char(1),
      Utleggingsdato char(1), Utleggingsmetode char(1), Utligger char(1), Utløsende værfohold char(1), Utsatt gruppe char(1), Utslipp av CO char(1), Utslipp av CO2 char(1), Utslipp av NOX char(1), Utstyr char(1), Utstyrsid char(1), Utstyrsnummer char(1), Utstyrstype char(1), Utvendig belysning char(1), VDB-register char(1), Vaktordning char(1), Vann i skjæring char(1), Vanndybde, normal char(1), Vannfølsomhet char(1), Vannmengde char(1), Vannoverdekning char(1), Varetransport hverdag u lørdag periode 1 fra kl char(1), Varetransport hverdag u lørdag periode 1 til kl char(1), Varetransport hverdag u lørdag periode 2 fra kl char(1), Varetransport hverdag u lørdag periode 2 til kl char(1), Varetransport lørdag fra char(1), Varetransport lørdag til char(1), Variasjon char(1), Varmekabler char(1), Varselblink påmontert char(1), Varsling med infrarødt lys char(1),
      Varsling på veg char(1), Vaskeplass for trailere char(1), Vassdragsnavn char(1), Vassdragsnummer char(1), Vedlegg char(1), Vedlikeholdsansvarlig char(1), Vedlikeholdsavtale char(1), Vedtaksdato char(1), Vedtaksnummer char(1), Vedtakstidspunkt fredning char(1), Vedtakstidspunkt regulering char(1), Vedtatt til år char(1), Veg lagt ut i vann char(1), Vegavstand fra hinder char(1), Vegbanereflektor char(1), Vegbredde char(1), Vegbredde, maks char(1), Vegbredde, min char(1), Vegbredde, totalt char(1), Vegbreddefordeling char(1), Vegdekkeklasse char(1), Vegfunksjon char(1), Veggruppe char(1), Vegident, generert char(1), Vegkategori char(1), Vegklasse char(1), Veglengde char(1), Vegnavn char(1), Vegnormaldata char(1), Vegnummer char(1),
      VegobjekttypeID char(1), Vegstatus char(1), VegstatusOver char(1), Vegtype char(1), Veiing char(1), Verdi, endelig char(1), Verdi, naturtype char(1), Verdi, teoretisk char(1), Verdi, usikkerhet char(1), Verdibeskrivelse char(1), Verneform char(1), Verneformål char(1), Verneforskrift char(1), Vernestatus char(1), Verneverdi/omfang char(1), Versjon av VSTØY/VLUFT char(1), Versjon av vluft/vstøy char(1), Vesentlige skader char(1), Viktighetsgrad char(1), Viltgjerde char(1), Viltreflektor char(1), Vindretning char(1), Vindustype i vegg mot hovedveg char(1), Vinkel char(1), Vinterdriftsklasse char(1), Vinterforberedelse char(1), Vinterlagring char(1), Vinterstengning char(1), Vinterstengt, fra dato char(1), Vinterstengt, til dato char(1),
      Vinteråpen char(1), Visflate char(1), Vlenkeid char(1), Volum char(1), Volum av skredmasser på veg char(1), Volum av totale skredmasser char(1), Vurdering dato char(1), Værforhold char(1), Værforhold på vegen char(1), Værstasjon 1 char(1), Værstasjon 2 char(1), Weather char(1), Web-adresse char(1), Wiredimensjon char(1), YDT char(1), gFDB_Id char(1), nFDB_Id char(1), slip% char(1), ÅDT char(1), ÅDT - 90 % verdi char(1), ÅDT i beregningsår char(1), ÅDT år char(1), ÅDT, andel lange kjøretøy char(1), ÅDT, slutt char(1), ÅDT, start char(1), ÅDT, total char(1), ÅDT-fordeling char(1), ÅDT-lang char(1), ÅDT-total char(1), Ådt buss char(1),
      Åpen atkomst til vann for dyrearter char(1), Åpningsår char(1), År, gjelder for char(1), Årlig tilskudd fra Statens vegvesen char(1), Årsak char(1), Årsak til skade/mangel char(1), Årsmodell på kjøretøy char(1), Årstall char(1), Øvre etasjenummer char(1), Øvre nominelle steinstørrelse char(1)
    -> AttributeCreator
Note: Link to fetch data / (original example: A cool tunnel) / This link may use the search endpoint / nvdb/api/sok?kriterie={json-object}, / or the nvdb/api/vegobjekter / endpoint
AttributeCreator
    ATTR_LIST = vegobjektURI_withMotherRelation,https://www.vegvesen.no/nvdb/api/vegobjekter/objekt/429703013,vegobjektURI,https://www.vegvesen.no/nvdb/api/vegobjekter/objekt/359603347
    -> HTTPFetcher
NVDB_features: Inspector

Bookmark: Fetch NVDB object(s)
HTTPFetcher
    TARGET_URL = @Value(vegobjektURI)
    REQUEST_HEADER = Accept:application/vnd.vegvesen.nvdb-v1+xml
    STATUS_CODE_ATTR = _http_status_code
    SAVE_FILE = No
    PROXY_AUTH_METHOD = Basic
    FOLLOW_REDIRECTS = Yes
    RESPONSE_HEADER_LIST_ATTR = _headers
    ERROR_ATTR = _error
    USE_COOKIES = No
    VERIFY_SSL_CERTIFICATES = Yes
    AUTH_METHOD = Basic
    TARGET_ATTR = _url_contents
    -> XMLFeatureMapper
Note: This is where the magic happens! / xml=>FME features
XMLFeatureMapper
    NEW_ATTRIBUTES = modifisert objektId objektTypeId objektTypeNavn sluttdato startdato strekningslengde BESTAR_AV{} ER_DEL_AV{} politiDistrikt region geometriUtm33 kontraktsomrade{} riksvegrute{} vegreferanse_fraMeter{} vegreferanse_tilMeter{} vegreferanse_fylke{} vegreferanse_hp{} vegreferanse_kategori{} vegreferanse_kommune{} vegreferanse_nummer{} vegreferanse_status{} veglenke_Id{} veglenke_til{} veglenke_fra{} veglenke_sidepos{} veglenke_felt{} veglenke_direction{}
    MERGE_ATTRS = No
    ATTRIBUTE_XML = _url_contents
    FEATURE_COUNT_PER_XML = _xml_feature_count_
    CONFIGURATION_TYPE = Single xfMap file
    SINGLE_XFMAP = $(FME_MF_DIR)xfmapDefintion_nvdbapi2fme.xml
    XML_INPUT_TYPE = Attribute with XML document
    XML_SOURCE_NAME = _xml_source_
    FEATURE_TYPE_ATTR = _xml_feature_type_
    MAPPED -> CoordinateSystemSetter
CoordinateSystemSetter
    COORDSYS = EPSG:25833
    -> GeometryReplacer
GeometryReplacer
    SOURCE = @Value(geometriUtm33)
    REMOVE_ATTRIBUTE = No
    KIND_LONG = OGC Well Known Text
    -> PythonCaller
Note: Removing empty elements / Equvalent of attribute remover / (but way cooler!) / Snipped from FME community / http://goo.gl/hRa3Lu
PythonCaller
    PYTHONSOURCE:
      # Snipped from user Sean at the FME community
      # http://fmepedia.safe.com/AnswersQuestionDetail?id=906a0000000coqvAAA#!/feedtype=SINGLE_QUESTION_SEARCH_RESULT&id=906a0000000ce45AAA
      import fmeobjects

      # Template Class Interface:
      class FeatureProcessor(object):
         def __init__(self):
             pass
         def input(self,feature):
             for tmpAttrName in feature.getAllAttributeNames():
                 tmpAttrVal = feature.getAttribute(tmpAttrName)

                 if (tmpAttrVal is None) or (tmpAttrVal == '') or (tmpAttrVal == 'NullValue'):
                     feature.removeAttribute(tmpAttrName)

             self.pyoutput(feature)
         def close(self):
             pass
    PYTHONSYMBOL = FeatureProcessor
    -> ListExploder
    -> ListExploder_2
    -> NVDB_features

Bookmark: List of descendants ("daughters")
Note: List of "daughter" objects / BESTAR_AV{} / 0 to N elements
ListExploder
    INDEX_ATTR = _element_index
    MODE = List Element Attributes
    LIST_ATTR = BESTAR_AV{}
    LIST_FOUND -> AttributeCreator_2
AttributeCreator_2
    ATTR_LIST = vegobjektURI,https://www.vegvesen.no/nvdb/api@Value(BESTAR_AV)
    -> Daughters
Note: Create valid link to each of those objects
Daughters: Inspector

Bookmark: Link to ancestor object ("Mother")
Note: Create valid link to each of those objects
Note: List of Mother object / ER_DEL_AV{} / Typically 0 or 1 elements
ListExploder_2
    INDEX_ATTR = _element_index
    MODE = List Element Attributes
    LIST_ATTR = ER_DEL_AV{}
    LIST_FOUND -> AttributeCreator_3
AttributeCreator_3
    ATTR_LIST = vegobjektURI,https://www.vegvesen.no/nvdb/api@Value(ER_DEL_AV)
    -> Mother
Mother: Inspector
